[DOCUMENT]
MID: 6a9745098a87daf19a7c487f89f39640
TITLE: StrictDoc Low-Level Requirements Specification (L3)
VERSION: Git commit: @GIT_VERSION, Git branch: @GIT_BRANCH
DATE: @GIT_COMMIT_DATETIME
PREFIX: SDOC-LLR-
OPTIONS:
  ENABLE_MID: True

[GRAMMAR]
ELEMENTS:
- TAG: SECTION
  PROPERTIES:
    IS_COMPOSITE: True
    VIEW_STYLE: Narrative
  FIELDS:
  - TITLE: MID
    TYPE: String
    REQUIRED: False
  - TITLE: UID
    TYPE: String
    REQUIRED: False
  - TITLE: TITLE
    TYPE: String
    REQUIRED: True
- TAG: TEXT
  FIELDS:
  - TITLE: MID
    TYPE: String
    REQUIRED: True
  - TITLE: UID
    TYPE: String
    REQUIRED: False
  - TITLE: STATEMENT
    TYPE: String
    REQUIRED: False
- TAG: REQUIREMENT
  PROPERTIES:
    VIEW_STYLE: Table
  FIELDS:
  - TITLE: MID
    TYPE: String
    REQUIRED: False
  - TITLE: UID
    TYPE: String
    REQUIRED: False
  - TITLE: STATUS
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  RELATIONS:
  - TYPE: Parent
  - TYPE: File

[TEXT]
MID: 1ea652f0284940b6913a0a224492759f
STATEMENT: >>>
The level 3 low-level requirements specification of StrictDoc (L3/LLR) is derived from StrictDoc's L2 high-level (L2/HLR) requirements specification. The purpose of L3/LLR is to provide the lowest-level requirements from which StrictDoc's source code can be directly implemented without further information.

It is at the L3 level that the StrictDoc requirements are specified for the actual software implementers, including both the StrictDoc developers and AI agents such as Codex. At the same time, the L2/HLR requirements provide the framework for the WHAT and WHY of the implementation instructions that are specified by this L3/LLR.

NOTE: This specification level is under construction. Many L2/HLR requirements will be gradually moved to be here at the L3/HLR level.
<<<

[[SECTION]]
MID: 408105d13e234f8aa73d017404eb5349
TITLE: Markdown text markup

[REQUIREMENT]
MID: 34246811634c493dbc771ae4c8bc3b14
UID: SDOC-LLR-183
STATUS: Active
TITLE: Read Markdown markup
STATEMENT: >>>
StrictDoc shall support reading Markdown files into in-memory SDoc documents.
<<<
RELATIONS:
- TYPE: Parent
  VALUE: SDOC-SRS-202

[REQUIREMENT]
MID: 476d094833ac4b02af1d72ad27710b36
UID: SDOC-LLR-197
STATUS: Active
TITLE: Write Markdown markup
STATEMENT: >>>
StrictDoc shall support writing in-memory SDoc documents to Markdown files.
<<<
RELATIONS:
- TYPE: Parent
  VALUE: SDOC-SRS-202

[REQUIREMENT]
MID: bc3b1411634c493dbc771ae4c8bc3b14
UID: SDOC-LLR-192
STATUS: Active
TITLE: Markdown files discovery
STATEMENT: >>>
StrictDoc shall discover Markdown files ``*.md`` and ``*.markdown`` using the same mechanism as used for SDoc files.
<<<
RELATIONS:
- TYPE: Parent
  VALUE: SDOC-SRS-202
- TYPE: Parent
  VALUE: SDOC-SRS-115

[REQUIREMENT]
MID: 245378eed60245378de2e099facd196d
UID: SDOC-LLR-196
STATUS: Active
TITLE: Identical Markdown content by import/export roundtrip
STATEMENT: >>>
StrictDoc shall ensure that identical Markdown content is produced every time StrictDoc reads a Markdown file and then writes it to another Markdown file.

The following aspects shall additionally apply:

- For MVP, line-endings should support both LF (Linux/macOS-style) and CRLF (Windows-style).
- The ``export --formats=markdown`` shall work for any format readable by StrictDoc, including Markdown itself, SDoc, RDF (future growth), ReqIF, etc.

NOTE: The write-back to Markdown file must happen through proper AST serialization, not just by giving back the original read Markdown source.

Exceptions:

Edge cases related to handling non-default input formats are postponed after the Markdown MVP is implemented. For example:

- Markdown reader encounters content format #3 (implicit field) via [LINK: SDOC-LLR-185], but writer always emits #1/#2 for content via [LINK: SDOC-LLR-198]. In this case the content will not be identical, but it is accepted for an MVP implementation.
<<<
RATIONALE: >>>
A consistent import/export roundtrip implementation and testing reduces the risk of the Markdown bi-directional import/export corruption.
<<<
RELATIONS:
- TYPE: Parent
  VALUE: SDOC-SSS-94

[REQUIREMENT]
MID: 11634c11634c493dbc771ae4c8bc3b14
UID: SDOC-LLR-191
STATUS: Active
TITLE: Markdown formats
STATEMENT: >>>
StrictDoc shall rely only on CommonMark core syntax v0.31.2 for SDoc node recognition.
<<<
RATIONALE: >>>
CommonMark core is the most portable target across parsers.
<<<

[REQUIREMENT]
MID: 41351111634c493dbc771ae4c8bc3b14
UID: SDOC-LLR-186
STATUS: Active
TITLE: Meta fields vs content fields
STATEMENT: >>>
StrictDoc shall recognize the following Markdown nodes as SDoc nodes:

.. code-block:: markdown

    ### Node title
    (empty line)
    **Meta field name 1**:
    **Meta field name 2**:
    ...
    (empty line)
    **Note content field 1**: ...
    (empty line)
    **Note content field 2**: ...
    ...

An SDoc node terminates when another Markdown section header or an EOF is encountered.

NOTE: There are no limitations to node level. A Markdown node can be at level 2, 3, etc. The level 1 is served for a root document node (document title with optional fields).
<<<

[REQUIREMENT]
MID: 54321111634c493dbc771ae4c8bc3b14
UID: SDOC-LLR-189
STATUS: Active
TITLE: One Markdown file — One SDoc document
STATEMENT: >>>
StrictDoc shall parse Markdown files using the "one Markdown file — one SDoc document" principle.
<<<

[REQUIREMENT]
MID: 12111111634c493dbc771ae4c8bc3b14
UID: SDOC-LLR-195
STATUS: Active
TITLE: Strict ban for redundant empty lines
STATEMENT: >>>
When a parsing Markdown file, if StrictDoc encounters two or more consecutive empty lines and the lines are not within a Markdown code block or a Markdown blockquote block, StrictDoc shall raise a StrictDocSemanticError.

NOTE: Empty lines includes whitespace-only lines which StrictDoc shall ban as well.
<<<

[REQUIREMENT]
MID: 999f59ede0f2477181bfc7667684df59
UID: SDOC-LLR-194
STATUS: Active
TITLE: Syntax for meta and content field names
STATEMENT: >>>
StrictDoc shall recognize the meta and content field names according to the following rules:

- Format is: ``**Field name**:``.
- Alphanumeric character range, separated by spaces, underscores or dashes.

Examples:

- ``**Statement**:``
- ``**STATEMENT**:``
- ``**IMPORTANT_STATEMENT**:``
- ``**SPDX-Req-ID**:``
<<<

[REQUIREMENT]
MID: 69f077ede0f2477181bfc7667684df59
UID: SDOC-LLR-184
STATUS: Active
TITLE: Three conventions for meta fields
STATEMENT: >>>
StrictDoc shall support reading out SDoc nodes out of Markdown sections arranged in the following way:

1) Requirements with meta-information stored in bullet point list:

.. code-block:: markdown

    ### Requirement title

    - **MID**: abcdabcdabcdabcdabcdabcdabcdabcdabcd
    - **UID**: REQ-001
    - **Status**: Draft

     System A shall do B.

When a Markdown title is followed by a full empty line followed by a bullet list and the bullet list follows the format ``- **<Name>**: <Value>``, the bullet list must be treated as a list of meta fields. The bullet list is terminated by one empty line.

2) Requirements with meta-information stored in consecutive lines separated by the "\\" character:

.. code-block:: markdown

    ### Requirement title

    **MID**: abcdabcdabcdabcdabcdabcdabcdabcdabcd \
    **UID**: REQ-001 \
    **Status**: Draft

    System A shall do B.

When a Markdown title is followed by a full empty line followed by list of lines in the format ``**<Name>**: <Value> \``, the list must be treated as a list of meta fields.
The line list is terminated by one empty line. The last line shall not end with a "\" character.

3) Requirements with meta-information stored in consecutive lines separated by the two empty space characters (as officially supported by Markdown):

.. code-block:: markdown

    ### Requirement title

    **MID**: abcdabcdabcdabcdabcdabcdabcdabcdabcd<two spaces>
    **UID**: REQ-001<two spaces>
    **Status**: Draft<two spaces>

    System A shall do B.

When a Markdown title is followed by a full empty line followed by list of lines in the format ``**<Name>**: <Value><two spaces>``, the list must be treated as a list of meta fields. The list is terminated by one empty line.

Each given node must follow only one of these three syntaxes. If StrictDoc encounters that a single node has more one or more fields of a mixed style, it must give up parsing this node as a valid node, and treat it as a non-normative SECTION/TEXT node.

As of Markdown MVP, the default and preferred syntax: shall be #2 with backslashes.
<<<

[REQUIREMENT]
MID: 111111ede0f2477181bfc7667684df59
UID: SDOC-LLR-185
STATUS: Active
TITLE: Valid formats for multi-line fields
STATEMENT: >>>
StrictDoc shall recognize SDoc node multiline fields from the following three formats

1) Explicit field name:

.. code-block:: markdown

    ### Requirement title

    - **MID**: abcdabcdabcdabcdabcdabcdabcdabcdabcd

     **Statement**: System A shall do B.

2) Explicit field name with a line break:

.. code-block:: markdown

    ### Requirement title

    - **MID**: abcdabcdabcdabcdabcdabcdabcdabcdabcd

     **Statement**:

     System A shall do B.

3) Implicit field name with a line break:

.. code-block:: markdown

    ### Requirement title

    **MID**: abcdabcdabcdabcdabcdabcdabcdabcdabcd

    System A shall do B.

    **Rationale**: This requirement is important because XYZ.

In this case, StrictDoc shall recognize the ``System A shall do B.`` as if it was written as ``**Statement**: System A shall do B.`` and recognize the rationale part as an explicitly written multiline field.

As of Markdown MVP, the default and preferred syntax shall be:

- #1 for values with single-line or single-paragraph/block strings.
- #2 for values with multiple markdown blocks separated by full empty lines.
<<<

[REQUIREMENT]
MID: 121eb00caee34e3fa6eaa683f211a472
UID: SDOC-LLR-202
STATUS: Active
TITLE: Support node parent relations
STATEMENT: >>>
StrictDoc shall support node relations in Markdown using the meta field:

.. code-block:: markdown

    **Relations**: <UID-1>, <UID-2>, ...

When reading Markdown:
- Each UID from the Relations field shall be converted to a relation with TYPE: Parent and VALUE: <UID>.
- All extra spaces shall be normalized before parsing to canonical ``<UID-1>, <UID-2>, ...``.
- The Markdown reader shall not check whether any UID actually exists. This task is deferred to the traceability index builder.

When writing Markdown, SDoc node relations with TYPE: Parent and no ROLE shall be serialized back to the same Relations field as a comma-separated UID list.

NOTE: For MVP, relation roles and Child relation types are out of scope.

NOTE: If the Relations field is not placed as the meta field but as the content field, StrictDoc shall raise a ``StrictDocSemanticError``.
<<<

[REQUIREMENT]
MID: 84df59ede0f2477181bfc7667684df59
UID: SDOC-LLR-193
STATUS: Active
TITLE: Valid SDoc node criteria
STATEMENT: >>>
StrictDoc shall recognize a Markdown node as a valid SDoc node when the Markdown node meets the following criteria:

- The node has one of the meta-fields: MID or UID.
- The node has an explicit or implicit content field.
- All node fields, meta or content, have a valid syntax.
- All node fields, meta or content, are valid default SDoc grammar fields.
<<<

[REQUIREMENT]
MID: 2f3a565aa60340369689eef45cbe7c9c
UID: SDOC-LLR-200
STATUS: Active
TITLE: Valid SDoc document root node
STATEMENT: >>>
StrictDoc shall recognize a root Markdown node as a valid SDoc document node when the said Markdown node meets the following criteria:

- The node has zero or more valid meta-fields.
- The valid metafields must satisfy [LINK: SDOC-LLR-194] and be formatted according to one meta syntax from [LINK: SDOC-LLR-184].

**Example: Valid DOCUMENT (title and metadata) + SECTION:**

.. code-block:: markdown

    # Document title

    **MID**: abcdabcdabcdabcdabcdabcdabcdabcdabcd \
    **UID**: DOC-001 \
    **Author**: John Doe

    ## Hello world

Such a description shall translate to an SDoc document with:

- DOCUMENT node with a title "Document title" and meta fields (MID, UID, Author).
- SECTION node with a title "Hello world".

**Example: Valid DOCUMENT (title and metadata) + TEXT:**

.. code-block:: markdown

    # Document title

    **MID**: abcdabcdabcdabcdabcdabcdabcdabcdabcd \
    **UID**: DOC-001 \
    **Author**: John Doe

    Hello world.

Such a description shall translate to an SDoc document with:

- DOCUMENT node with a title "Document title" and meta fields (MID, UID, Author).
- TEXT node with a statement "Hello world.".

**Example: Valid DOCUMENT (title, no metadata) + TEXT:**

.. code-block:: markdown

    # Document title

    MID: abc

    Hello world.

Such a description shall translate to an SDoc document with:

- DOCUMENT node with a title "Document title" and no meta fields.
- TEXT node with a statement "MID: abc\\n\\nHello world.".
<<<

[REQUIREMENT]
MID: 11133111634c493dbc771ae4c8bc3b14
UID: SDOC-LLR-190
STATUS: Active
TITLE: Reading rules — Default grammar for MVP
STATEMENT: >>>
When a parsing Markdown file, StrictDoc shall generate an SDoc document using the default SDoc grammar according to the following rules:

- The only supported node for MVP shall be REQUIREMENT, TEXT and SECTION nodes with no other nodes supported.
- A valid SDoc node shall be recognized as REQUIREMENT. The Markdown's node title becomes the REQUIREMENT node's TITLE.
- If a Markdown node cannot be recognized as a valid SDoc node, the node shall recognize the said Markdown node's title as a SECTION node with a TITLE field set to the title and the node's body as a regular (non-normative) TEXT SDoc node, not as a normative SDoc node. The TEXT node's statement shall contain the Markdown node's body.
- All field names shall be capitalized when created to SDoc field objects. For example, ``Statement`` becomes ``STATEMENT``. At the same time, the original field names must be written to the document's grammar as-is. For example, a ``**Rationale**:`` becomes ``RATIONALE`` in the SDoc field name and ``Rationale`` in the human title.
- StrictDoc shall defer the validation of MID/UID uniqueness across nodes to the TraceabilityIndexBuilder class.
- If a given field name appears more than once in a node, StrictDoc shall raise a StrictDocSemanticError.
- If a node is otherwise invalid and also has duplicate fields, the parser shall treat this node as SECTION and TEXT without raising errors.
- All SDoc node fields, REQUIREMENT/TEXT/SECTION, must store all field values' Markdown content verbatim, without any pre-processing. This includes preserving original whitespace/line endings exactly.
<<<

[REQUIREMENT]
MID: 44c2dffd898345f39a384bcdacc01b5e
UID: SDOC-LLR-199
STATUS: Active
TITLE: Reading rules — Node hierarchy
STATEMENT: >>>
When a parsing Markdown file, StrictDoc shall generate an SDoc document using the default SDoc grammar according to the following rules:

- The first content of a Markdown file shall always be a level 1 ``#`` node with the document title, followed by an optional set of metafields that translate to SDoc document meta (DocumentConfig/custom_metadata). The syntax for metafields shall be the same to meta fields of a regular markdown node. For MVP, all metafields shall be written as custom_metadata, with no reserved fields are considered.

- When the root L1 document title node with (optional meta fields) are recognized, StrictDoc shall treat all following text as a TEXT node until any other header node starts.

- If StrictDoc can recognize the root L1 document node title but no valid metadata, StrictDoc shall treat all following text as a TEXT node until any other header node starts.

- When root metadata has a valid syntax but has invalid semantics (duplicated fields), StrictDoc shall raise StrictDocSemanticError.

- No other node can be at level 1 except the document title, otherwise StrictDocSemanticError must be raised.

- The Markdown node hierarchy shall be strictly consecutive in forward direction:

  - If a node level forward jump is encountered, for example L1->L3, StrictDoc shall raise a StrictDocSemanticError, regardless of whether the node is valid SDoc node or invalid.

- The node level jumps in backward direction, for example L4->L2, are allowed if the node with a lower level results at level 2 or higher.
<<<

[REQUIREMENT]
MID: c144739494ad4f75b65b9286248005eb
UID: SDOC-LLR-198
STATUS: Active
TITLE: Writing rules — Default grammar for MVP
STATEMENT: >>>
When writing an SDoc document to a markdown file, StrictDoc shall generate the Markdown markup according to the following rules:

- The meta fields shall be written:

  - Using the format #2 for new documents not coming from file system (using backslashes for all meta-field lines but last one).
  - Using the format that was auto-detected during reading a Markdown file in case the file is already on the disk and follows a certain convention. The detection shall be detected at a file level and memorized individually by each SDoc document.

- The content fields shall be written using formats #1 (Explicit field name) for single-paragraph fields and #2 (Explicit field name with a line break) for multi-paragraph fields. A multi-paragraph field is one that results in multiple markdown paragraphs/blocks each separated visually by a full empty line.

- StrictDoc shall write the SDoc fields as Markdown fields based on SDoc human title as recorded in the document grammar element field human title. If a human title is missing in the grammar, the field name shall be used.

- All fields shall be printed in the same order like they are stored in an SDoc node. Meta vs content decision shall be based on a standard SDocNode/GrammarElement decision for multiline index.

- The node level shall be used for defining the Markdown node level. The document title becomes the top-level section level 1. SDoc node level 1 becomes ``##``, level 2 becomes ``###``, etc.
<<<

[REQUIREMENT]
MID: 987111ede0f2477181bfc7667684df59
UID: SDOC-LLR-187
STATUS: Active
TITLE: Robust Markdown backend
STATEMENT: >>>
StrictDoc shall employ a well-maintained Markdown library with Python support.
<<<

[[/SECTION]]

[[SECTION]]
MID: 65cfed23d9bb404cad88dadc95feb0d1
TITLE: HTML2PDF export

[REQUIREMENT]
MID: 95f0e0198d8446a38eb1c7fc0f409522
UID: SDOC-LLR-203
TITLE: Use of html2pdf4doc
STATEMENT: >>>
StrictDoc shall export HTML documents using html2pdf4doc library with the following document types supported already:

- StrictDoc's main DOC document type/screen.
<<<
RATIONALE: >>>
html2pdf4doc is part of the StrictDoc project that is developed by the core team. It allows printing PDF pages directly from StrictDoc HTML and gives the developers a full control over the printing mechanics.
<<<

[REQUIREMENT]
MID: 335b11da872245c0bf09c82d5909db0e
UID: SDOC-LLR-204
STATUS: Active
TITLE: Use of PyPDF for PDF postprocessing
STATEMENT: >>>
StrictDoc shall employ the PyPDF library for the following tasks:

- Rewriting all StrictDoc's LINK/ANCHOR to documents of the same project tree into the PDF anchors.
<<<
RATIONALE: >>>
The extra processing with PyPDF is needed because there are limitations of what developers can do when printing HTML to PDF with html2pdf4doc based on Google Chrome Driver.
<<<
RELATIONS:
- TYPE: Parent
  VALUE: SDOC-SRS-203

[REQUIREMENT]
MID: 272338e1e8f244eca573348660464b09
UID: SDOC-LLR-205
STATUS: Active
TITLE: Cross-linking PDF documents from one project tree
STATEMENT: >>>
When exporting HTML documents to PDF, StrictDoc shall rewrite all LINK/ANCHOR to documents of the same project tree into the PDF document links/anchors according to the following rule:

- The Chrome Driver resolves the relative links to other documents with full paths, e.g., ``file:///<full-path-to-another-SDoc-document>-PDF.html#<anchor>``.
- The PDF postprocessing step shall convert these absolute ``file:///...` links to just relative paths: ``<relative-path-to-another-SDoc-document>.pdf`` without the leading slash character.
- If one PDF is in a nested folder compared to another PDF, the link to this PDF anchor shall have relative ``../`` path components.
<<<
RATIONALE: >>>
Allows a reader to navigate between PDF documents of the same project as requested by the parent requirement.
<<<
COMMENT: >>>
The PDF cross-document linking is supported by the PDF format natively but is known to not work in all PDF viewers. For example, it is known to work well in Linux PDF viewers, but not macOS Preview viewer.
<<<
RELATIONS:
- TYPE: Parent
  VALUE: SDOC-SRS-203

[[/SECTION]]

[[SECTION]]
MID: 7055d55c999d4c46bdfc847038a00978
TITLE: Source code parsing

[[SECTION]]
MID: e18dcfcb9b99459d9c7f560f35d01ff8
TITLE: Rust

[REQUIREMENT]
MID: d83cab2dcd014d328b348acc37c6f4a6
UID: SDOC-LLR-164
TITLE: Auto-scoped relation markers in Rust docs
STATEMENT: >>>
If a StrictDoc relation marker is inside a `Rust doc comment`_, the marker scope shall be set to exact the item the Rust
language defines as target of the containing doc comment. The :code:`@relation(scope=...)` parameter shall therefore
be optional and shall be ignored if provided.

.. code-block:: rust
   :number-lines:

   /// @relation(REQ-1)
   impl Foo {

       /// @relation(REQ-2)
       fn foo() {
       }
   }

In the given example, the first marker shall link REQ-1 to the :code:`impl Foo` implementation,
highlighting lines 1 to 7. The second marker shall link REQ-2 to the :code:`fn foo()` function,
highlighting lines 4 to 6.

.. _Rust doc comment: https://doc.rust-lang.org/rust-by-example/meta/doc.html#doc-comments
<<<
COMMENT: >>>
Note that doc comments are syntactic sugar for `doc attribute`_ s, which shall also be supported.
To figure detailed doc comment rules from the rust-lang specification it's sometimes useful
to check for general attribute rules, if explicit doc comment rules are missing.

.. _doc attribute: https://doc.rust-lang.org/rustdoc/write-documentation/the-doc-attribute.html
<<<
RELATIONS:
- TYPE: Parent
  VALUE: SDOC-SRS-34
- TYPE: Parent
  VALUE: SDOC-SRS-137
- TYPE: Parent
  VALUE: SDOC-SRS-204

[REQUIREMENT]
MID: 91c7b9fd9c514327bb012639cdf1515b
UID: SDOC-LLR-165
STATUS: Active
TITLE: Inner doc attributes
STATEMENT: >>>
StrictDoc shall support relation markers in inner_ `doc attribute`_ s.

.. _inner: https://doc.rust-lang.org/reference/attributes.html#r-attributes.inner
.. _doc attribute: https://doc.rust-lang.org/rustdoc/write-documentation/the-doc-attribute.html#the-doc-attribute
<<<
RELATIONS:
- TYPE: Parent
  VALUE: SDOC-SRS-204

[REQUIREMENT]
MID: 002bfab5383e4cb785049c4738651f43
UID: SDOC-LLR-166
STATUS: Active
TITLE: Inner line docs
STATEMENT: >>>
StrictDoc shall support auto-scoped relation relation markers in `inner line docs`_.

.. _inner line docs: https://doc.rust-lang.org/reference/comments.html#grammar-INNER_LINE_DOC
<<<
RELATIONS:
- TYPE: Parent
  VALUE: SDOC-SRS-204

[REQUIREMENT]
MID: d04b97d76cc848f982610035bf7d3dc2
UID: SDOC-LLR-167
STATUS: Active
TITLE: Inner block docs
STATEMENT: >>>
StrictDoc shall support auto-scoped relation relation markers in `inner block docs`_.

.. _inner block docs: https://doc.rust-lang.org/reference/comments.html#grammar-INNER_BLOCK_DOC
<<<
RELATIONS:
- TYPE: Parent
  VALUE: SDOC-SRS-204

[REQUIREMENT]
MID: 84b351267cfc4e16b3ff2c5db654e9f0
UID: SDOC-LLR-168
STATUS: Active
TITLE: Outer doc attributes
STATEMENT: >>>
StrictDoc shall support auto-scoped relation markers in outer_ `doc attribute`_ s.

.. _outer: https://doc.rust-lang.org/reference/attributes.html#r-attributes.outer
.. _doc attribute: https://doc.rust-lang.org/rustdoc/write-documentation/the-doc-attribute.html#the-doc-attribute
<<<
RELATIONS:
- TYPE: Parent
  VALUE: SDOC-SRS-204

[REQUIREMENT]
MID: 171978da9f8f4f40b52fb7599caa67e6
UID: SDOC-LLR-169
STATUS: Active
TITLE: Outer line docs
STATEMENT: >>>
StrictDoc shall support auto-scoped relation markers in `outer line docs`_.

.. _outer line docs: https://doc.rust-lang.org/reference/comments.html#grammar-OUTER_LINE_DOC
<<<
RELATIONS:
- TYPE: Parent
  VALUE: SDOC-SRS-204

[REQUIREMENT]
MID: 1a8d558fbe244621818b6242be365638
UID: SDOC-LLR-170
STATUS: Active
TITLE: Outer block docs
STATEMENT: >>>
StrictDoc shall support auto-scoped relation markers in `outer block docs`_.

.. _outer block docs: https://doc.rust-lang.org/reference/comments.html#railroad-OUTER_BLOCK_DOC
<<<
RELATIONS:
- TYPE: Parent
  VALUE: SDOC-SRS-204

[REQUIREMENT]
MID: e1be1f38dd374f82abd9691d081f293b
UID: SDOC-LLR-171
STATUS: Active
TITLE: File, line and range markers
STATEMENT: >>>
StrictDoc shall point to lines and line ranges of Rust code by using file, line and range markers.
These marker types shall be parsed from `regular line and block comments`_.

Note: File markers may also result from the inner doc comments of the top-level module.

.. _regular line and block comments: https://doc.rust-lang.org/rust-by-example/hello/comment.html#comments
<<<
RELATIONS:
- TYPE: Parent
  VALUE: SDOC-SRS-139
- TYPE: Parent
  VALUE: SDOC-SRS-124
- TYPE: Parent
  VALUE: SDOC-SRS-138
- TYPE: Parent
  VALUE: SDOC-SRS-204

[REQUIREMENT]
MID: b9b2e4d377db42f5b3fb7aeabaf3f72a
UID: SDOC-LLR-172
STATUS: Active
TITLE: Source nodes from doc comments
STATEMENT: >>>
If a Rust doc comments contains custom tags, and the containing Rust source file matches an entry in the
source node configuration, StrictDoc shall create document nodes from the custom tags and automatically
link the created node with the Rust item targeted by the doc comment.
<<<
RELATIONS:
- TYPE: Parent
  VALUE: SDOC-SRS-141
- TYPE: Parent
  VALUE: SDOC-SRS-204

[REQUIREMENT]
MID: 9d7e371ad7a146e1968cd9bbb7a6790f
UID: SDOC-LLR-173
STATUS: Active
TITLE: Forward relations to Rust items
STATEMENT: >>>
StrictDoc shall support linking from a requirement in SDoc to a language item in Rust code by using a :code:`FILE`
relation of type :code:`FUNCTION`. For example

.. code-block:: strictdoc

   [REQUIREMENT]
   UID: REQ-1
   RELATIONS:
   - TYPE: File
     VALUE: file.rs
     FUNCTION: file::foo

This shall work for all kinds of Rust items that have a `canonical path`_, including const, enum, fn, mod, static,
struct, trait, type, union.

.. _canonical path: https://doc.rust-lang.org/reference/paths.html#canonical-paths
<<<
RELATIONS:
- TYPE: Parent
  VALUE: SDOC-SRS-204

[REQUIREMENT]
MID: d01b2204fcb44882b991ca11ce567f52
UID: SDOC-LLR-174
STATUS: Active
TITLE: Forward relation by canonical path
STATEMENT: >>>
The identifier for forward relations shall be the `canonical path`_ as the rustc compiler would set it when invoked for
a single file like

.. code-block:: shell

   rustc --crate-type rlib --emit=obj src/lib.rs

Note: :code:`cargo build` usually result in a different canonical path, since it considers the file position relative to
the crate root. Using a single file as root is a simplification, needed because StrictDoc is unaware of the Rust
file and directory-based module hierarchy.

.. _canonical path: https://doc.rust-lang.org/reference/paths.html#canonical-paths
<<<
COMMENT: >>>
The canonical path of an item can be observed with :code:`objdump -t lib.o --demangle=rust`. For example, given this
source file

.. code-block:: rust
   :number-lines:

   pub mod foo {

       pub trait Foo {
           fn foo(&self) {}
       }

       pub struct Bar(i32);

       impl Foo for Bar {
           fn foo(&self) {}
       }
   }

:code:`objdump` will show

.. code-block:: shell

   <lib::foo::Bar as lib::foo::Foo>::foo

Alas, a forward relation would be

.. code-block:: strictdoc

   [REQUIREMENT]
   UID: REQ-1
   RELATIONS:
   - TYPE: File
     VALUE: file.rs
     FUNCTION: <lib::foo::Bar as lib::foo::Foo>::foo
<<<
RELATIONS:
- TYPE: Parent
  VALUE: SDOC-SRS-204

[REQUIREMENT]
MID: 04b5927294c34710995d3671040dd8ae
UID: SDOC-LLR-175
STATUS: Active
TITLE: Collapse doc comments
STATEMENT: >>>
Multiple scattered doc comments shall be collapsed as done by the rustdoc_ tool when using the collapse-docs option
to determine the highlight range(s).

For example, rustdoc would collapse alle these comments into the description of :code:`fn foo()`

.. code-block:: rust
   :number-lines:

   /// Some
   /// line

   /// doc,

   /**
     * and some
     * block dock,
     */

   #[doc = "and some"]

   #[doc = "doc attr."]

   fn foo() {
   }

In the given example, the StrictDoc highlight range for the relation marker shall be from line 1 to line 16.

.. _rustdoc: https://github.com/rust-lang/rust/tree/main/src/tools/rustdoc
<<<
RELATIONS:
- TYPE: Parent
  VALUE: SDOC-SRS-204

[REQUIREMENT]
MID: e67e8258177847138112589e606c0413
UID: SDOC-LLR-176
STATUS: Active
TITLE: Rust marker descriptions
STATEMENT: >>>
StrictDoc should use the marker labels as rustdoc_ would set them in the description of a documented node.

.. _rustdoc: https://doc.rust-lang.org/stable/rustdoc/
<<<
RELATIONS:
- TYPE: Parent
  VALUE: SDOC-SRS-204

[REQUIREMENT]
MID: 7bf3f26c335741398a50e9679a0d4c84
UID: SDOC-LLR-177
STATUS: Active
TITLE: Valid positions of doc comments
STATEMENT: >>>
StrictDoc shall find doc comments where the language allows_ them and ignore those in other positions.

.. _allows: https://doc.rust-lang.org/reference/attributes.html#r-attributes.allowed-position
<<<
COMMENT: >>>
Since doc comments are syntactic sugar for doc attributes, allowed position rules for attributes apply.
<<<
RELATIONS:
- TYPE: Parent
  VALUE: SDOC-SRS-204

[REQUIREMENT]
MID: 5e9645177af14db7b5fcaba0298a328b
UID: SDOC-LLR-178
STATUS: Active
TITLE: Inner doc comments for functions
STATEMENT: >>>
StrictDoc shall find inner doc comments in function blocks.
<<<
RELATIONS:
- TYPE: Parent
  VALUE: SDOC-SRS-204

[REQUIREMENT]
MID: b70a27cc49f54b0bb7e7956b055957a4
UID: SDOC-LLR-179
STATUS: Active
TITLE: Inner doc comments for modules
STATEMENT: >>>
StrictDoc shall find inner doc comments in module blocks.
<<<
RELATIONS:
- TYPE: Parent
  VALUE: SDOC-SRS-204

[REQUIREMENT]
MID: 012e605921954430ab6c11e245fb7378
UID: SDOC-LLR-180
STATUS: Active
TITLE: Inner doc comments for external blocks
STATEMENT: >>>
StrictDoc shall find inner doc comments in external blocks.
<<<
RELATIONS:
- TYPE: Parent
  VALUE: SDOC-SRS-204

[REQUIREMENT]
MID: 2d955dd847954556aa5a32018a7c41fd
UID: SDOC-LLR-181
STATUS: Active
TITLE: Inner doc comments for implementation blocks
STATEMENT: >>>
StrictDoc shall find inner doc comments in implementation blocks.
<<<
RELATIONS:
- TYPE: Parent
  VALUE: SDOC-SRS-204

[REQUIREMENT]
MID: ef8849024b78477496620eb1bf081900
UID: SDOC-LLR-182
STATUS: Active
TITLE: Allowed position for outer docs
STATEMENT: >>>
StrictDoc shall find outer doc comments in `allowed positions`_ as specified by the Rust language:

- All item_ declarations
- Most statements
- Block expressions, but only when they are the outer expression of an
  expression statement or the final expression of another block expression.
- Enum variants, struct and union fields
- Generic lifetime or type parameter
- Expressions in limited situations
- Function, closure and function pointer parameters

.. _allowed positions: https://doc.rust-lang.org/reference/attributes.html#r-attributes.allowed-position
.. _item: https://doc.rust-lang.org/reference/items.html#r-items.syntax
<<<
RELATIONS:
- TYPE: Parent
  VALUE: SDOC-SRS-204

[[/SECTION]]

[[/SECTION]]

[[SECTION]]
MID: 0feab4cce32f44dc85f5dee8a3c934df
TITLE: Collaborative review comments

[REQUIREMENT]
MID: 6916661164fd4c7384931aabd8f4edf0
UID: SDOC-LLR-220
TITLE: The DISCUSSION: field
STATEMENT: >>>
StrictDoc shall define a reserved multi-line field ``DISCUSSION:``. It shall appear as the last field of the node.

The field shall store collaborative review comments and their resolutions.

The field shall be strictly formatted as an YAML-compatible dictionary where:

- the dictionary keys act as anchors
- A specific span ID key (e.g., ``c-12345:``) anchors the thread to an inline markup span.
- The reserved generic key ``node:`` anchors the thread to the enclosing requirement or section itself.
- The dictionary values are unordered lists (using hyphens -) representing individual comments in a thread.
- continuation lines are indented by exactly 2-spaces


EXAMPLE:

.. code ::

    STATEMENT: >>>
    The system shall shut down [safely]{#c-12345}.
    <<<
    DISCUSSION: >>>
    node:

    - 2023-10-24T10:00:00Z user_C: This entire requirement needs a safety review.

    c-12345:

    - 2023-10-24T10:30:00Z user_A: Should we define "safely"?
    - 2023-10-25T10:35:22Z user_B: Good point, I will update the statement.
      I noticed that we use "safely" also in requirement XYZ.
    - 2023-10-25T:10:39:00Z user_B: [RESOLVED]
    <<<
<<<
RATIONALE: >>>
The format aligns well with YAML, Markdown, and reStructuredText standard conventions, making it intuitive for users to read and easy for the back-end to parse.

Using the reserved ``node:`` key strictly scopes the comment to the current block, preventing accidentally anchoring comments to wrong nodes when UID are updated manually.

The structure minimizes git merge conflicts, as each new comment is a new line.
<<<

[REQUIREMENT]
MID: a689eedb097642b59903bc0da3e8f02f
UID: SDOC-LLR-221
TITLE: Inline span markup
STATEMENT: >>>
StrictDoc shall support inline span markup within all multi-line text fields (e.g., ``STATEMENT``, ``RATIONALE``) to anchor comment threads to specific text fragments.

The syntax shall follow the attribute extension pattern: ``[marked text]{#thread-id}``.

- ``[marked text]`` defines the text fragment under review
- ``{#thread-id}`` assigns a unique identifier that shall match a corresponding key in the node's ``DISCUSSION:`` field

During document generation (e.g. PDF, static HTML, Docutils/Sphinx), the rendering engine shall strip the markup and output only the marked text.

In the Web Editor, the engine shall transform the markup into a HTML span to eable highlighting and interaction.
<<<

[REQUIREMENT]
MID: 98e68dc5692e4a53b4ae3ccbc66e4e92
UID: SDOC-LLR-222
TITLE: Add collaborative comment action
STATEMENT: >>>
The StrictDoc Web Editor shall provide an "Add Collaborative Comment" action. Triggering this action shall create an ephemeral UI state, which depend on the user's text selection:

- **Inline comment (text selected):**

  If text is selected within a multi-line node field, the editor shall apply a temporary visual highlight to the selected text, and open a new comment input card in the sidebar.

-  **Node-level comment (no selection):**

   If no text is selected, the editor shall open a new comment input card in the sidebar, bound to the current node.

- **Cancellation:**

  If the user closes the input card without saving, the editor shall discard the UI state and clear the temporary highlight.

- **Saving:**

  If the user closes the input card by clicking save, the editor shall call the save_collaborative_comment endpoint on the backend.
<<<
RATIONALE: >>>
Context-dependent behavior enables both inline and node-level comments through a single interaction, which is intuitive for the user.

Keeping the initialization phase strictly ephemeral prevents the creation of orphaned spans or empty dictionary keys if a user abandons their comment
<<<

[REQUIREMENT]
MID: 8c23149460c94f0faa73c4cac7af3e05
UID: SDOC-LLR-223
STATEMENT: >>>
The StrictDoc Web Editor shall provide passive visual indicators for existing discussion threads:

- Inline Thread Visibility: Text bounded by an inline span (e.g., ``[text]{#id}``) shall be rendered with a distinct, low-intrusion style (e.g., a dashed underline) to differentiate it from standard text.

- Node Thread Visibility: Nodes containing a ``node:`` level discussion thread shall display a visual badge (e.g., an icon and comment count) adjacent to the node.
<<<

[REQUIREMENT]
MID: 690a6039be0a43f6a687c157ed0144b0
UID: SDOC-LLR-224
TITLE: Save collaborative comment endpoint (back-end)
STATEMENT: >>>
The StrictDoc server shall provide an ``action/document/save_collaborative_comment`` endpoint, which
<<<

[[/SECTION]]
